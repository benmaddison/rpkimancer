RpkiFoo

DEFINITIONS EXPLICIT TAGS ::=
BEGIN

IMPORTS
  CONTENT-TYPE FROM CryptographicMessageSyntax-2009 -- in [RFC5911]
    { iso(1) member-body(2) us(840) rsadsi(113549) pkcs(1)
      pkcs-9(9) smime(16) modules(0) id-mod-cms-2004-02(41) } ;

ct-rpkiFooObject CONTENT-TYPE ::=
    { TYPE RpkiFooObject IDENTIFIED BY
      id-ct-rpkiFooObject }

id-ct-rpkiFooObject OBJECT IDENTIFIER ::=
    { iso(1) member-body(2) us(840) rsadsi(113549) pkcs(1)
      pkcs-9(9) id-smime(16) id-ct(1) 999 }

RpkiFooObject ::= OCTET STRING

END
