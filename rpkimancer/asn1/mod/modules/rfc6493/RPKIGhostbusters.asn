RPKIGhostbusters

DEFINITIONS EXPLICIT TAGS ::=

BEGIN

-- EXPORTS ALL --

IMPORTS
    CONTENT-TYPE FROM CryptographicMessageSyntax-2009
        { iso(1) member-body(2) us(840) rsadsi(113549)
          pkcs(1) pkcs-9(9) smime(16) modules(0) id-mod-cms-2004-02(41) } ;


-- Ghostbusters Content Type
ct-rpkiGhostbusters CONTENT-TYPE ::=
   { TYPE GhostbustersRecord IDENTIFIED BY id-ct-rpkiGhostbusters }

-- Ghostbusters Content Type: OID

id-smime OBJECT IDENTIFIER ::= { iso(1) member-body(2)
us(840) rsadsi(113549) pkcs(1) pkcs9(9) 16 }

id-ct OBJECT IDENTIFIER ::= { id-smime 1 }

id-ct-rpkiGhostbusters OBJECT IDENTIFIER ::= { id-ct 35 }

-- Ghostbusters Content Type: eContent

GhostbustersRecord ::= OCTET STRING

END
