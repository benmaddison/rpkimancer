-- 
-- ASN.1 module found by ../tools/crfc2asn1.pl in ../../draft-rpki-checklists/draft-spaghetti-sidrops-rpki-rsc.txt at line 183
-- 

RpkiSignedChecklist-2021
    { iso(1) member-body(2) us(840) rsadsi(113549)
      pkcs(1) pkcs9(9) smime(16) mod(0) 49 }

DEFINITIONS EXPLICIT TAGS ::=
BEGIN

IMPORTS
CONTENT-TYPE, Digest, DigestAlgorithmIdentifier
FROM CryptographicMessageSyntax-2009 -- in [RFC5911]
  { iso(1) member-body(2) us(840) rsadsi(113549) pkcs(1)
    pkcs-9(9) smime(16) modules(0) id-mod-cms-2004-02(41) }

DummyType, -- pycrate can't seem to import the first name, so pad the list
ASIdOrRange, IPAddressFamily
FROM IPAddrAndASCertExtn -- in [RFC3779]
  { iso(1) identified-organization(3) dod(6) internet(1)
    security(5) mechanisms(5) pkix(7) mod(0)
    id-mod-ip-addr-and-as-ident(30) } ;

ct-rpkiSignedChecklist CONTENT-TYPE ::=
  { RpkiSignedChecklist IDENTIFIED BY id-ct-signedChecklist }

id-ct-signedChecklist OBJECT IDENTIFIER ::=
  { iso(1) member-body(2) us(840) rsadsi(113549) pkcs(1)
    pkcs-9(9) id-smime(16) id-ct(1) 49 }

RpkiSignedChecklist ::= SEQUENCE {
version  [0]          INTEGER DEFAULT 0,
resources             ResourceBlock,
digestAlgorithm       DigestAlgorithmIdentifier,
checkList             SEQUENCE SIZE (1..MAX) OF FileAndHash }

FileAndHash ::= SEQUENCE {
file            IA5String,
hash            Digest }

ResourceBlock ::= SEQUENCE {
  asID         [0]       AsList OPTIONAL,
  ipAddrBlocks [1]       IPList OPTIONAL }
  -- at least one of asID or ipAddrBlocks MUST be present
  ( WITH COMPONENTS { ..., asID PRESENT} |
    WITH COMPONENTS { ..., ipAddrBlocks PRESENT } )

AsList ::= SEQUENCE (SIZE(1..MAX)) OF ASIdOrRange

IPList ::= SEQUENCE (SIZE(1..MAX)) OF IPAddressFamily

END
